#!/usr/bin/env python
# -*- coding: utf-8 -*-

"""
FreeCAD MCP Server Addon
========================
Runs a TCP socket server inside FreeCAD that accepts JSON
commands from an external MCP bridge process.

Install:
  1. Copy this file to FreeCAD's Macro folder
     (Macro → Macros → "User macros location")
  2. Macro → Execute Macro → FreeCADMCP.FCMacro
  3. Click "Start Server"
  4. Run freecad_mcp_server.py externally
"""

# ── Configuration ──────────────────────────────────
DEFAULT_PORT = 9876

# ── Imports ────────────────────────────────────────
import FreeCAD
import Part
import json
import socket
import traceback
import math
import os
import builtins
import re
import tempfile

try:
    import FreeCADGui
    HAS_GUI = True
except ImportError:
    FreeCADGui = None
    HAS_GUI = False

try:
    from PySide2 import QtCore, QtGui, QtWidgets
except ImportError:
    try:
        from PySide6 import QtCore, QtGui, QtWidgets
    except ImportError:
        from PySide import QtCore, QtGui
        QtWidgets = QtGui


# ═══════════════════════════════════════════════════
# MCP SOCKET SERVER
# ═══════════════════════════════════════════════════

class FreeCADMCPServer:
    """
    Non-blocking TCP server that runs inside FreeCAD.
    Accepts JSON commands and executes them in the FreeCAD context.
    Uses QTimer so the GUI stays responsive.
    """

    def __init__(self, host="localhost", port=DEFAULT_PORT):
        self.host = host
        self.port = port
        self.running = False
        self.server_socket = None
        self.client_socket = None
        self.buffer = b""
        self.timer = None

    # ── Lifecycle ──────────────────────────────

    def start(self):
        if self.running:
            return
        self.server_socket = socket.socket(socket.AF_INET, socket.SOCK_STREAM)
        self.server_socket.setsockopt(socket.SOL_SOCKET, socket.SO_REUSEADDR, 1)
        try:
            self.server_socket.bind((self.host, self.port))
            self.server_socket.listen(1)
            self.server_socket.setblocking(False)
            self.timer = QtCore.QTimer()
            self.timer.timeout.connect(self._poll)
            self.timer.start(100)          # 10 Hz
            self.running = True
            FreeCAD.Console.PrintMessage(
                f"[FreeCAD-MCP] Server listening on {self.host}:{self.port}\n"
            )
        except Exception as e:
            FreeCAD.Console.PrintError(f"[FreeCAD-MCP] Bind failed: {e}\n")
            self.stop()

    def stop(self):
        self.running = False
        if self.timer:
            self.timer.stop()
            self.timer = None
        for s in (self.client_socket, self.server_socket):
            if s:
                try:
                    s.close()
                except Exception:
                    pass
        self.client_socket = None
        self.server_socket = None
        self.buffer = b""
        FreeCAD.Console.PrintMessage("[FreeCAD-MCP] Server stopped\n")

    # ── Polling (runs on Qt main thread) ───────

    def _poll(self):
        if not self.running:
            return

        # Accept new client
        if self.client_socket is None and self.server_socket:
            try:
                self.client_socket, addr = self.server_socket.accept()
                self.client_socket.setblocking(False)
                FreeCAD.Console.PrintMessage(
                    f"[FreeCAD-MCP] Client connected: {addr}\n"
                )
            except BlockingIOError:
                pass
            except Exception as e:
                FreeCAD.Console.PrintError(
                    f"[FreeCAD-MCP] Accept error: {e}\n"
                )

        # Read from client
        if self.client_socket:
            try:
                data = self.client_socket.recv(65536)
                if data:
                    self.buffer += data
                    # Try to decode one complete JSON object
                    try:
                        command = json.loads(self.buffer.decode("utf-8"))
                        self.buffer = b""
                        response = self._route(command)
                        payload = json.dumps(response).encode("utf-8")
                        self.client_socket.sendall(payload)
                    except json.JSONDecodeError:
                        pass  # partial message — wait for more
                else:
                    # Client disconnected
                    FreeCAD.Console.PrintMessage(
                        "[FreeCAD-MCP] Client disconnected\n"
                    )
                    self.client_socket.close()
                    self.client_socket = None
                    self.buffer = b""
            except BlockingIOError:
                pass
            except Exception as e:
                FreeCAD.Console.PrintError(
                    f"[FreeCAD-MCP] Recv error: {e}\n"
                )
                try:
                    self.client_socket.close()
                except Exception:
                    pass
                self.client_socket = None
                self.buffer = b""

    # ── Command Router ─────────────────────────

    def _route(self, command):
        cmd = command.get("type", "")
        params = command.get("params", {})

        HANDLERS = {
            "ping":               self.cmd_ping,
            "get_scene_info":     self.cmd_get_scene_info,
            "create_object":      self.cmd_create_object,
            "modify_object":      self.cmd_modify_object,
            "delete_object":      self.cmd_delete_object,
            "get_object_info":    self.cmd_get_object_info,
            "execute_code":       self.cmd_execute_code,
            "boolean_operation":  self.cmd_boolean_operation,
            "fillet_edges":       self.cmd_fillet_edges,
            "chamfer_edges":      self.cmd_chamfer_edges,
            "export_model":       self.cmd_export_model,
            "set_color":          self.cmd_set_color,
            "fit_view":           self.cmd_fit_view,
            "capture_view":       self.cmd_capture_view,
            "new_document":       self.cmd_new_document,
            "clear_document":     self.cmd_clear_document,
        }

        handler = HANDLERS.get(cmd)
        if not handler:
            return {"status": "error",
                    "message": f"Unknown command: {cmd}",
                    "available": list(HANDLERS.keys())}
        try:
            result = handler(**params)
            return {"status": "success", "result": result}
        except Exception as e:
            tb = traceback.format_exc()
            FreeCAD.Console.PrintError(f"[FreeCAD-MCP] {cmd}: {e}\n")
            return {"status": "error", "message": str(e), "traceback": tb}

    # ── Helpers ─────────────────────────────────

    def _ensure_doc(self):
        if FreeCAD.ActiveDocument is None:
            FreeCAD.newDocument("MCP_Model")
        return FreeCAD.ActiveDocument

    def _find_obj(self, name):
        doc = self._ensure_doc()
        obj = doc.getObject(name)
        if obj:
            return obj
        for o in doc.Objects:
            if o.Label == name:
                return o
        raise ValueError(f"Object not found: '{name}'")

    def _obj_dict(self, obj):
        """Serialize a FreeCAD object to a JSON-safe dict."""
        d = {
            "name": obj.Name,
            "label": obj.Label,
            "type": obj.TypeId,
            "placement": {
                "x": round(obj.Placement.Base.x, 4),
                "y": round(obj.Placement.Base.y, 4),
                "z": round(obj.Placement.Base.z, 4),
            },
        }
        for prop in ("Length", "Width", "Height",
                      "Radius", "Radius1", "Radius2"):
            if hasattr(obj, prop):
                d[prop.lower()] = round(float(getattr(obj, prop)), 4)

        if HAS_GUI and hasattr(obj, "ViewObject"):
            vo = obj.ViewObject
            d["visible"] = vo.Visibility
            try:
                c = vo.ShapeColor
                d["color"] = [round(c[0], 3), round(c[1], 3), round(c[2], 3)]
            except Exception:
                pass
        return d

    def _recompute(self):
        doc = self._ensure_doc()
        doc.recompute()

    def _fit(self):
        if HAS_GUI:
            try:
                v = FreeCADGui.ActiveDocument.ActiveView
                if v:
                    v.fitAll()
            except Exception:
                pass

    # ═══════════════════════════════════════════
    # COMMAND HANDLERS
    # ═══════════════════════════════════════════

    def cmd_ping(self):
        ver = FreeCAD.Version()
        return {
            "alive": True,
            "freecad_version": f"{ver[0]}.{ver[1]}",
            "has_gui": HAS_GUI,
            "document": (FreeCAD.ActiveDocument.Name
                         if FreeCAD.ActiveDocument else None),
        }

    # ── Scene ──────────────────────────────────

    def cmd_get_scene_info(self):
        doc = self._ensure_doc()
        objects = [self._obj_dict(o) for o in doc.Objects]
        return {
            "document_name": doc.Name,
            "document_label": doc.Label,
            "object_count": len(objects),
            "objects": objects,
        }

    # ── Create ─────────────────────────────────

    def cmd_create_object(self, type="BOX", name=None,
                          location=None, rotation=None, **kw):
        doc = self._ensure_doc()
        t = type.upper()

        if t == "BOX":
            obj = doc.addObject("Part::Box", name or "Box")
            obj.Length = kw.get("length", 10)
            obj.Width  = kw.get("width",  10)
            obj.Height = kw.get("height", 10)
        elif t == "CYLINDER":
            obj = doc.addObject("Part::Cylinder", name or "Cylinder")
            obj.Radius = kw.get("radius", 5)
            obj.Height = kw.get("height", 10)
        elif t == "SPHERE":
            obj = doc.addObject("Part::Sphere", name or "Sphere")
            obj.Radius = kw.get("radius", 5)
        elif t == "CONE":
            obj = doc.addObject("Part::Cone", name or "Cone")
            obj.Radius1 = kw.get("radius1", 10)
            obj.Radius2 = kw.get("radius2", 0)
            obj.Height  = kw.get("height",  10)
        elif t == "TORUS":
            obj = doc.addObject("Part::Torus", name or "Torus")
            obj.Radius1 = kw.get("radius1", 20)
            obj.Radius2 = kw.get("radius2", 5)
        else:
            raise ValueError(
                f"Unknown type '{type}'. "
                "Use: BOX, CYLINDER, SPHERE, CONE, TORUS"
            )

        if name:
            obj.Label = name
        if location:
            obj.Placement.Base = FreeCAD.Vector(*location)
        if rotation:
            if len(rotation) == 4:
                obj.Placement.Rotation = FreeCAD.Rotation(
                    FreeCAD.Vector(*rotation[:3]), rotation[3])
            elif len(rotation) == 3:
                obj.Placement.Rotation = FreeCAD.Rotation(*rotation)

        self._recompute()
        self._fit()
        return self._obj_dict(obj)

    # ── Modify ─────────────────────────────────

    def cmd_modify_object(self, name, location=None,
                          rotation=None, visible=None,
                          label=None, **kw):
        obj = self._find_obj(name)

        if location:
            obj.Placement.Base = FreeCAD.Vector(*location)
        if rotation:
            if len(rotation) == 4:
                obj.Placement.Rotation = FreeCAD.Rotation(
                    FreeCAD.Vector(*rotation[:3]), rotation[3])
            elif len(rotation) == 3:
                obj.Placement.Rotation = FreeCAD.Rotation(*rotation)
        if visible is not None and HAS_GUI:
            obj.ViewObject.Visibility = visible
        if label:
            obj.Label = label

        DIM_MAP = {
            "length": "Length", "width": "Width", "height": "Height",
            "radius": "Radius", "radius1": "Radius1", "radius2": "Radius2",
        }
        for k, v in kw.items():
            prop = DIM_MAP.get(k.lower())
            if prop and hasattr(obj, prop):
                setattr(obj, prop, float(v))

        self._recompute()
        return self._obj_dict(obj)

    # ── Delete ─────────────────────────────────

    def cmd_delete_object(self, name):
        doc = self._ensure_doc()
        obj = self._find_obj(name)
        info = {"deleted_name": obj.Name, "deleted_label": obj.Label}
        doc.removeObject(obj.Name)
        self._recompute()
        return info

    # ── Info ───────────────────────────────────

    def cmd_get_object_info(self, name):
        obj = self._find_obj(name)
        info = self._obj_dict(obj)

        if hasattr(obj, "Shape"):
            s = obj.Shape
            info["shape"] = {
                "volume_mm3": round(s.Volume, 2),
                "area_mm2":   round(s.Area, 2),
                "faces":      len(s.Faces),
                "edges":      len(s.Edges),
                "vertices":   len(s.Vertexes),
                "bbox": {
                    "min": [round(s.BoundBox.XMin, 2),
                            round(s.BoundBox.YMin, 2),
                            round(s.BoundBox.ZMin, 2)],
                    "max": [round(s.BoundBox.XMax, 2),
                            round(s.BoundBox.YMax, 2),
                            round(s.BoundBox.ZMax, 2)],
                },
            }

        props = {}
        for p in obj.PropertiesList:
            try:
                val = getattr(obj, p)
                if isinstance(val, (int, float, str, bool)):
                    props[p] = val
            except Exception:
                pass
        info["properties"] = props
        return info

    # ── Execute Arbitrary Code ─────────────────

    def cmd_execute_code(self, code):
        doc = self._ensure_doc()
        ns = {
            "__builtins__": builtins,
            "FreeCAD": FreeCAD, "App": FreeCAD,
            "Part": Part,
            "doc": doc, "document": doc,
            "Vector": FreeCAD.Vector,
            "Placement": FreeCAD.Placement,
            "Rotation": FreeCAD.Rotation,
            "math": math,
        }

        try:
            exec(code, ns)
            doc.recompute()
            self._fit()
            return {"executed": True,
                    "message": "Code executed successfully"}
        except Exception as e:
            tb = traceback.format_exc()
            # Extract line info
            m = re.search(r'File .+, line (\d+)', tb)
            line_info = ""
            if m:
                lineno = int(m.group(1))
                lines = code.split("\n")
                if 1 <= lineno <= len(lines):
                    line_info = f" | line {lineno}: {lines[lineno-1].strip()}"
            raise Exception(f"{type(e).__name__}: {e}{line_info}")

    # ── Boolean Operations ─────────────────────

    def cmd_boolean_operation(self, operation, base, tool, name=None):
        doc = self._ensure_doc()
        base_obj = self._find_obj(base)
        tool_obj = self._find_obj(tool)

        op = operation.lower()
        if op == "cut":
            result = doc.addObject("Part::Cut", name or "Cut")
        elif op in ("fuse", "union", "join"):
            result = doc.addObject("Part::Fuse", name or "Fuse")
        elif op in ("common", "intersect", "intersection"):
            result = doc.addObject("Part::Common", name or "Common")
        else:
            raise ValueError(
                f"Unknown operation '{operation}'. Use: cut, fuse, common"
            )

        result.Base = base_obj
        result.Tool = tool_obj
        if name:
            result.Label = name

        if HAS_GUI:
            base_obj.ViewObject.Visibility = False
            tool_obj.ViewObject.Visibility = False

        self._recompute()
        self._fit()
        return self._obj_dict(result)

    # ── Fillet / Chamfer ───────────────────────

    def cmd_fillet_edges(self, name, radius=1.0):
        doc = self._ensure_doc()
        obj = self._find_obj(name)
        if not hasattr(obj, "Shape"):
            raise ValueError(f"'{name}' has no shape")
        edges = obj.Shape.Edges
        if not edges:
            raise ValueError(f"'{name}' has no edges")
        fillet = obj.Shape.makeFillet(float(radius), edges)
        r = doc.addObject("Part::Feature", f"{obj.Label}_Fillet")
        r.Shape = fillet
        r.Label = f"{obj.Label}_Fillet"
        if HAS_GUI:
            obj.ViewObject.Visibility = False
        self._recompute()
        self._fit()
        return self._obj_dict(r)

    def cmd_chamfer_edges(self, name, size=1.0):
        doc = self._ensure_doc()
        obj = self._find_obj(name)
        if not hasattr(obj, "Shape"):
            raise ValueError(f"'{name}' has no shape")
        edges = obj.Shape.Edges
        if not edges:
            raise ValueError(f"'{name}' has no edges")
        chamfer = obj.Shape.makeChamfer(float(size), edges)
        r = doc.addObject("Part::Feature", f"{obj.Label}_Chamfer")
        r.Shape = chamfer
        r.Label = f"{obj.Label}_Chamfer"
        if HAS_GUI:
            obj.ViewObject.Visibility = False
        self._recompute()
        self._fit()
        return self._obj_dict(r)

    # ── Export ──────────────────────────────────

    def cmd_export_model(self, filepath, format=None):
        doc = self._ensure_doc()
        if not format:
            format = os.path.splitext(filepath)[1].lstrip(".").lower()

        objs = [o for o in doc.Objects
                if hasattr(o, "Shape")
                and (not HAS_GUI
                     or not hasattr(o, "ViewObject")
                     or o.ViewObject.Visibility)]
        if not objs:
            raise ValueError("No visible shapes to export")

        d = os.path.dirname(os.path.abspath(filepath))
        if d:
            os.makedirs(d, exist_ok=True)

        if format in ("step", "stp", "iges", "igs", "brep"):
            Part.export(objs, filepath)
        elif format == "stl":
            try:
                import Mesh
                Mesh.export(objs, filepath)
            except ImportError:
                shapes = [o.Shape for o in objs]
                Part.makeCompound(shapes).exportStl(filepath)
        elif format == "fcstd":
            doc.saveAs(filepath)
        else:
            Part.export(objs, filepath)

        return {"exported": True, "filepath": filepath,
                "format": format, "objects": len(objs)}

    # ── Appearance ─────────────────────────────

    def cmd_set_color(self, name, color):
        if not HAS_GUI:
            return {"message": "No GUI — cannot set color"}
        obj = self._find_obj(name)
        r, g, b = color[0], color[1], color[2]
        if max(r, g, b) > 1:
            r, g, b = r / 255, g / 255, b / 255
        obj.ViewObject.ShapeColor = (r, g, b, 0.0)
        if len(color) >= 4:
            t = color[3]
            if t > 1:
                t = t / 255
            obj.ViewObject.Transparency = int(t * 100)
        return self._obj_dict(obj)

    # ── View ───────────────────────────────────

    def cmd_fit_view(self):
        self._fit()
        return {"fitted": True}

    def cmd_capture_view(self, filepath=None, width=800, height=600):
        if not HAS_GUI:
            return {"error": "No GUI available"}
        if not filepath:
            filepath = os.path.join(
                tempfile.gettempdir(), "freecad_capture.png"
            )
        d = os.path.dirname(os.path.abspath(filepath))
        if d:
            os.makedirs(d, exist_ok=True)
        view = FreeCADGui.ActiveDocument.ActiveView
        view.saveImage(filepath, width, height)
        return {"captured": True, "filepath": filepath,
                "width": width, "height": height}

    # ── Document ───────────────────────────────

    def cmd_new_document(self, name="MCP_Model"):
        doc = FreeCAD.newDocument(name)
        return {"document_name": doc.Name, "document_label": doc.Label}

    def cmd_clear_document(self):
        doc = self._ensure_doc()
        names = [o.Name for o in doc.Objects]
        for n in reversed(names):
            try:
                doc.removeObject(n)
            except Exception:
                pass
        doc.recompute()
        return {"cleared": True, "removed": len(names)}


# ═══════════════════════════════════════════════════
# UI PANEL
# ═══════════════════════════════════════════════════

class FreeCADMCPPanel(QtWidgets.QDialog):
    """Minimal control panel for the MCP server."""

    def __init__(self, parent=None):
        super().__init__(parent)
        self.server = None
        self._build()

    def _build(self):
        self.setWindowTitle("FreeCAD MCP")
        self.setFixedWidth(340)
        ly = QtWidgets.QVBoxLayout(self)
        ly.setSpacing(10)

        # Header
        hdr = QtWidgets.QLabel("FreeCAD MCP Server")
        hdr.setAlignment(QtCore.Qt.AlignCenter)
        hdr.setStyleSheet(
            "font-size:15px; font-weight:bold; "
            "padding:8px; color:#1565C0;"
        )
        ly.addWidget(hdr)

        # Status
        self.status = QtWidgets.QLabel("● Stopped")
        self.status.setAlignment(QtCore.Qt.AlignCenter)
        self.status.setStyleSheet(
            "padding:6px; border-radius:4px; font-weight:bold;"
            "background:#FFEBEE; color:#C62828;"
        )
        ly.addWidget(self.status)

        # Port
        row = QtWidgets.QHBoxLayout()
        row.addWidget(QtWidgets.QLabel("Port:"))
        self.port_spin = QtWidgets.QSpinBox()
        self.port_spin.setRange(1024, 65535)
        self.port_spin.setValue(DEFAULT_PORT)
        row.addWidget(self.port_spin)
        row.addStretch()
        ly.addLayout(row)

        # Start / Stop
        self.btn = QtWidgets.QPushButton("Start Server")
        self.btn.setMinimumHeight(38)
        self.btn.setStyleSheet(
            "QPushButton{font-size:13px;font-weight:bold;"
            "background:#43A047;color:white;border:none;"
            "border-radius:6px;padding:8px;}"
            "QPushButton:hover{background:#388E3C;}"
        )
        self.btn.clicked.connect(self._toggle)
        ly.addWidget(self.btn)

        # Instructions
        info = QtWidgets.QLabel(
            "1. Click Start Server\n"
            "2. Run freecad_mcp_server.py externally\n"
            "3. Connect Claude Desktop or any MCP client\n\n"
            "The MCP bridge connects to this socket and\n"
            "translates MCP tool calls → FreeCAD commands."
        )
        info.setWordWrap(True)
        info.setStyleSheet("color:#666; font-size:11px; padding:4px;")
        ly.addWidget(info)
        ly.addStretch()

    def _toggle(self):
        if self.server and self.server.running:
            self.server.stop()
            self.server = None
            self.btn.setText("Start Server")
            self.btn.setStyleSheet(
                "QPushButton{font-size:13px;font-weight:bold;"
                "background:#43A047;color:white;border:none;"
                "border-radius:6px;padding:8px;}"
            )
            self.status.setText("● Stopped")
            self.status.setStyleSheet(
                "padding:6px;border-radius:4px;font-weight:bold;"
                "background:#FFEBEE;color:#C62828;"
            )
            self.port_spin.setEnabled(True)
        else:
            port = self.port_spin.value()
            self.server = FreeCADMCPServer(port=port)
            self.server.start()
            if self.server.running:
                self.btn.setText("Stop Server")
                self.btn.setStyleSheet(
                    "QPushButton{font-size:13px;font-weight:bold;"
                    "background:#E53935;color:white;border:none;"
                    "border-radius:6px;padding:8px;}"
                )
                self.status.setText(f"● Listening on port {port}")
                self.status.setStyleSheet(
                    "padding:6px;border-radius:4px;font-weight:bold;"
                    "background:#E8F5E9;color:#2E7D32;"
                )
                self.port_spin.setEnabled(False)

    def closeEvent(self, event):
        if self.server and self.server.running:
            self.server.stop()
        super().closeEvent(event)


# ═══════════════════════════════════════════════════
# LAUNCH
# ═══════════════════════════════════════════════════

def launch():
    parent = None
    if HAS_GUI:
        try:
            parent = FreeCADGui.getMainWindow()
        except Exception:
            pass
    panel = FreeCADMCPPanel(parent=parent)
    panel.show()
    return panel

_mcp_panel = launch()
